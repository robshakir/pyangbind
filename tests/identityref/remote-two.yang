module remote-two {
    yang-version "1";
    namespace "http://rob.sh/yang/test/typedef/remote-two";
    prefix "remote-two";

    import identityref { prefix "i"; }

    organization "BugReports Inc";
    contact "A bug reporter";
    description
        "A test module";
    revision 2014-01-01 {
        description "april-fools";
        reference "fooled-you";
    }

    identity remote-id {
      base "i:local-base";
    }
}
