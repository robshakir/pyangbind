module split-classes {
    yang-version "1";
    namespace "http://rob.sh/yang/test/split-classes";
    prefix "remote";
    organization "BugReports Inc";
    contact "A bug reporter";

    description
        "A test module";
    revision 2014-01-01 {
        description "april-fools";
        reference "fooled-you";
    }

    container split-classes {
        leaf test {
            type string;
        }
    }

    container remote {
        container remote {
            container remote {
                leaf remote {
                    type string;
                }
            }
        }
    }

    container choices {
        choice choice-one {
            case case-one {
                container case-one-container {
                    list user {
                        key "username";
                        leaf username {
                            type string;
                        }
                    }
                }
            }

            case case-two {
                container case-two-container {
                    list user {
                        key "username";
                        leaf username {
                            type string;
                        }
                    }
                }
            }
        }
    }
}
