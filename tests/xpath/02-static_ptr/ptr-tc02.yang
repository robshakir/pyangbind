module ptr-tc02 {
    yang-version "1.1";
    namespace "http://rob.sh/yang/xpathelper/tc02";
    prefix "tc01";
    organization "BugReports Inc";
    contact "A bug reporter";

    description
        "A test module";
    revision 2014-01-01 {
        description "april-fools";
        reference "fooled-you";
    }


    container container {

        list t1a {
            key "t1b";

            leaf t1b {
                type leafref {
                    path "../t1c/t1d";
                }
            }

            container t1c {
                leaf t1d {
                    type string;
                }
            }
        }
    }
}
