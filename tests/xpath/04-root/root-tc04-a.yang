module root-tc04-a {
    yang-version "1";
    namespace "http://rob.sh/yang/test/root-tc04-a";
    prefix "foo";
    organization "BugReports Inc";
    contact "A bug reporter";

    description
        "A test module";
    revision 2014-01-01 {
        description "april-fools";
        reference "fooled-you";
    }

    container root-tc04-a {
        leaf a {
            type string;
        }
    }
}
