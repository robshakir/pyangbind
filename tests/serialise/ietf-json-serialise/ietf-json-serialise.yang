module ietf-json-serialise {
  yang-version "1";
  namespace "http://rob.sh/yang/test/serialise/ietf-json";
  prefix "foo";

  import remote { prefix "remote"; }

  organization "BugReports Inc";
  contact "A bug reporter";

  description
      "A test module";
  revision 2014-01-01 {
      description "april-fools";
      reference "fooled-you";
  }

  identity id-base {
    description
      "base identity";
  }

  identity idone {
    base id-base;
  }

  identity idtwo {
    base id-base;
  }

  typedef derived64 {
    type uint64;
  }

  typedef decimaldefinedtype {
    type decimal64 {
      fraction-digits 2;
    }
  }

  typedef decimalrangetype {
    type decimal64 {
      fraction-digits 10;
      range "1..max";
    }
  }

  typedef definedtype {
    type string;
  }

  typedef definedtypeunion {
    type union {
      type uint8;
      type string;
    }
  }

  typedef nhopenum {
    type enumeration {
      enum DROP {}
    }
  }

  typedef regexstring {
    type string {
      pattern "[0-9]+\.[0-9]+\.[0-9]+\.[0-9]+";
    }
  }

  container c1 {
    list l1 {
      key "k1";

      leaf k1 {
          type uint32;
      }

      leaf empty {
        type empty;
      }

      leaf uint8 {
        type uint8;
      }

      leaf uint16 {
        type uint16;
      }

      leaf uint32 {
        type uint32;
      }

      leaf uint64 {
        type uint64;
      }

      leaf int8 {
        type int8;
      }

      leaf int16 {
        type int16;
      }

      leaf int32 {
        type int32;
      }

      leaf int64 {
        type int64;
      }

      leaf decleaf {
        type decimal64 {
          fraction-digits 4;
        }
      }

      leaf restricted-integer {
        type int8 {
          range "5..10";
        }
      }

      leaf string {
        type string;
      }

      leaf restricted-string {
        type string {
          pattern "a.*";
        }
      }

      leaf union {
        type union {
          type string;
          type uint32;
        }
      }

      leaf-list union-list {
        type union {
          type uint32;
          type string;
        }
      }

      leaf leafref {
        type leafref {
          path "/c1/t1/target";
        }
      }

      leaf binary {
        type binary;
      }

      leaf boolean {
        type boolean;
      }

      leaf enumeration {
        type enumeration {
          enum one;
          enum two;
        }
      }

      leaf identityref {
        type identityref {
          base id-base;
        }
      }

      leaf remote-identityref {
        type identityref {
          base remote:cheese;
        }
      }

      leaf typedef-one {
        type definedtype;
      }

      leaf typedef-two {
        type definedtypeunion;
      }

      choice test-choice {
        case one {
          leaf one-leaf {
            type string;
          }
        }
        case two {
          leaf two-leaf {
            type string;
          }
        }
      }
      leaf-list ll {
        type string;
      }

      leaf-list next-hop {
        type union {
          type regexstring;
          type nhopenum;
          type string;
        }
      }

      leaf typedef-decimal {
        type decimaldefinedtype;
      }

      leaf range-decimal {
        type decimal64 {
          fraction-digits 10;
          range "1..10";
        }
      }

      leaf typedef-decimalrange {
        type decimalrangetype;
      }

      leaf uint64type {
        type derived64;
      }
    }

    list l2 {
      key "k1";
      ordered-by user;

      leaf k1 {
       type uint32;
      }
    }

    list t1 {
      key "target";
      leaf target {
        type string;
      }
    }
  }

  container augtarget {

  }
}
