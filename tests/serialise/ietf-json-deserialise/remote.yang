module remote {
  yang-version "1";
  namespace "http://rob.sh/yang/test/serialise/ietf-json-deserialise/remote";
  prefix "prefix-for-remote";
  organization "BugReports Inc";
  contact "A bug reporter";

  description
      "A test module";
  revision 2014-01-01 {
      description "april-fools";
      reference "fooled-you";
  }

  identity cheese {
    description "base";
  }

  identity stilton {
    base cheese;
  }
}
