module roundtrip {
  yang-version "1";
  namespace "http://rob.sh/yang/test/serialise/roundtrip";
  prefix "foo";
  organization "BugReports Inc";
  contact "A bug reporter";

  description
      "A test module";
  revision 2014-01-01 {
      description "april-fools";
      reference "fooled-you";
  }
  
  identity BASE;
  identity VALUE_ONE { base BASE; }

  container a {
    leaf idref {
      type identityref {
        base BASE;
      }
    }
  }
}
