module uint {
    yang-version "1";
    namespace "http://rob.sh/yang/test/uint";
    prefix "foo";
    organization "BugReports Inc";
    contact "A bug reporter";

    description
        "A test module";
    revision 2014-01-01 {
        description "april-fools";
        reference "fooled-you";
    }


    container issue-fixes {
      leaf region-id {
        // match attribute mode=type: name=regionId type=long
        type uint32 {
          // match constraint type=range: # values=1
          range "0..4294967295";
        }
        default "0";
      } // leaf region-id
    }

    container uint-container {
        description
            "A container";

        leaf eight {
            type uint8;
            description
              "A test leaf for uint8";
        }

        leaf eightdefault {
            type uint8;
            default 255;
            description
              "A test leaf for uint8 with a default";
        }

        leaf eightresult {
            type uint8;
            description
              "A test leaf that stores results of operations";
        }

        leaf sixteen {
            type uint16;
            description
              "A test leaf for uint16";
        }

        leaf sixteendefault {
            type uint16;
            default 65535;
            description
              "A test leaf for uint16 with a default";
        }

        leaf sixteenresult {
            type uint16;
            description
              "A test leaf that stores results of operations";
        }

        leaf thirtytwo {
            type uint32;
            description
              "A test leaf for uint32";
        }

        leaf thirtytwodefault {
            type uint32;
            default 4294967295;
            description
              "A test leaf for uint32 with a default";
        }

        leaf thirtytworesult {
            type uint32;
            description
              "A test leaf that stores results of operations";
        }

        leaf sixtyfour {
            type uint64;
            description
              "A test leaf for uint16";
        }

        leaf sixtyfourdefault {
            type uint64;
            default 18446744073709551615;
            description
              "A test leaf for uint16 with a default";
        }

        leaf sixtyfourresult {
            type uint64;
            description
              "A test leaf that stores results of operations";
        }

        leaf eightrestricted {
            type uint8 {
                range 1..10;
            }
            description
              "A test uint8 that has restricted range";
        }

        leaf sixteenrestricted {
            type uint16 {
                range 100..1000;
            }
            description
              "A test uint16 that has a restricted range";
        }

        leaf thirtytworestricted {
            type uint32 {
                range 10000..500000;
            }
            description
              "A test uint32 that has a restricted range";
        }

        leaf sixtyfourrestricted {
            type uint64 {
                range 800..173709551615;
            }
            description
              "A test uint32 that has a restricted range";
        }
    }
}
