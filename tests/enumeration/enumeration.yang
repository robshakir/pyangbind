module enumeration {
    yang-version "1";
    namespace "http://rob.sh/yang/test/enumeration";
    prefix "foo";
    organization "BugReports Inc";
    contact "A bug reporter";

    description
        "A test module";
    revision 2014-01-01 {
        description "april-fools";
        reference "fooled-you";
    }

    container "container" {
        description
          "A test container";

        leaf e {
            type enumeration {
                enum one;
                enum two {
                    value 42;
                }
                enum three;
            }
        }

       leaf f {
            type enumeration {
                enum a;
                enum b;
                enum c;
            }
            default c;
        }
    }
}
