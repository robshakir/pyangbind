module binary {
    yang-version "1";
    namespace "http://rob.sh/yang/test/binary";
    prefix "foo";
    organization "BugReports Inc";
    contact "A bug reporter";

    description
        "A test module";
    revision 2014-01-01 {
        description "april-fools";
        reference "fooled-you";
    }

    container container {
        leaf b1 {
            type binary;
            description
                "A test leaf";
        }

        leaf b2 {
            type binary;
            default "eWFuZw=="; /* yang */
            description
                "A test leaf with a default";
        }

        leaf b3 {
            type binary {
                length 2;
            }
        }

        leaf b4 {
            type binary {
                length 2..4;
            }
        }

        leaf b5 {
            type binary {
                length "2..4 | 6 | 10..42";
            }
        }
    }
}
