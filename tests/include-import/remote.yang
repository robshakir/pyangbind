module remote {
    yang-version "1";
    namespace "http://rob.sh/yang/test/include-import/remote";
    prefix "remote";
    organization "BugReports Inc";
    contact "A bug reporter";

    description
        "A test module";
    revision 2014-01-01 {
        description "april-fools";
        reference "fooled-you";
    }

    identity mammal; 

    typedef remote-definition {
        type string;
    }
}
