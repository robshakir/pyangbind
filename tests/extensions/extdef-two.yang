module extdef-two {
    yang-version "1";
    namespace "http://rob.sh/yang/test/extdef-two";
    prefix "foo";
    organization "BugReports Inc";
    contact "A bug reporter";

    description
        "A test module";
    revision 2014-01-01 {
        description "april-fools";
        reference "fooled-you";
    }

    extension extension-three {
        argument "extname";
    }

}
