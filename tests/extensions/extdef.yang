module extdef {
    yang-version "1";
    namespace "http://rob.sh/yang/test/extdef";
    prefix "foo";
    organization "BugReports Inc";
    contact "A bug reporter";

    description
        "A test module";
    revision 2014-01-01 {
        description "april-fools";
        reference "fooled-you";
    }

    extension extension-one {
        argument "extname";
    }

    extension extension-two {
        argument "extval";
    }

}
