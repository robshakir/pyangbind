module typedef {
    yang-version "1";
    namespace "http://rob.sh/yang/test/list";
    prefix "foo";

    import remote { prefix defn; }

    organization "BugReports Inc";
    contact "A bug reporter";

    description
        "A test module";
    revision 2014-01-01 {
        description "april-fools";
        reference "fooled-you";
    }

    typedef derived-string-type {
        type string;
    }

    typedef restricted-integer-type {
        type uint16 {
            range 0..64;
        }
    }

    typedef bgp-session-direction {
        type enumeration {
            enum INBOUND;
            enum OUTBOUND;
        }
    }

    typedef new-string-type {
        type string;
        default "defaultValue";
    }

    container container {
        description
            "A container";

        leaf string {
            type derived-string-type;
        }

        leaf integer {
            type restricted-integer-type;
        }

        leaf stringdefault {
            type derived-string-type;
            default "aDefaultValue";
        }

        leaf integerdefault {
            type restricted-integer-type;
            default 10;
        }

        leaf new-string {
            type new-string-type;
        }

        leaf remote-new-type {
            type defn:remote-definition;
        }

        leaf session-dir {
            type bgp-session-direction;
        }

        leaf remote-local-type {
            type defn:remote-local-definition;
        }
    }
}
