module string {
    yang-version "1";
    namespace "http://rob.sh/yang/test/string";
    prefix "foo";
    organization "BugReports Inc";
    contact "A bug reporter";

    description
        "A test module";
    revision 2014-01-01 {
        description "april-fools";
        reference "fooled-you";
    }

    container string-container {
        description
            "A container";

        leaf string-leaf {
            type string;
            description
              "A test leaf for a string test";
        }

        leaf string-default-leaf {
            type string;
            default "string";
            description
              "A string that has a default value";
        }

        leaf restricted-string {
            type string {
                pattern "^a";
            }
            description
                "A test leaf with a restriction that
                the string can only start with an a";
        }

        leaf restricted-string-default {
            type string {
                pattern "^b";
            }
            description
                "A test leaf with a restriction that
                the string can only start with a b
                and a default value";
            default "b";
        }
    }
}
